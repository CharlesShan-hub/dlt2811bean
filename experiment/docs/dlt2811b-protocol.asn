--
-- DL/T 2811 Protocol Layer — APCH / ASDU definitions
--
-- This is the foundation layer for all services.
--

DLT2811-Protocol { 1 2 156 2811 2 } DEFINITIONS AUTOMATIC TAGS ::= BEGIN

-- ======================================================================
-- IMPORTS from datatypes
-- ======================================================================

IMPORTS
    Int8U, Int16U, Int32U, VisibleString, OctetString
    FROM DLT2811-DataTypes;

-- ======================================================================
-- APCH — Application Protocol Control Header (4 bytes)
-- ======================================================================

-- Mapped to: CmsApch (Java)
Apch ::= SEQUENCE {
    cc          ControlCode,
    sc          Int8U,
    fl          Int16U
}

-- Mapped to: CmsControlCode (Java)
ControlCode ::= SEQUENCE {
    next        BOOLEAN,
    resp        BOOLEAN,
    err         BOOLEAN,
    pi          Int8U
}

-- ======================================================================
-- ASDU — Application Service Data Unit (base for all services)
-- ======================================================================

-- Mapped to: CmsAsdu (Java)
-- reqId is the first field in every ASDU
Asdu ::= SEQUENCE {
    reqId       Int16U
}

-- ======================================================================
-- APDU — Complete application-layer frame
-- ======================================================================

-- Mapped to: CmsApdu (Java)
Apdu ::= SEQUENCE {
    apch        Apch,
    asdu        OCTET STRING (SIZE(0..65531))
}

END
