--
-- DL/T 2811 Data Types ? ASN.1 Module
--
-- Generated from Cms* Java classes in com.ysh.dlt2811bean.datatypes
-- All type names correspond to ASN.1 type definitions from GB/T 45906.3.
-- Java prefix "Cms" is stripped for ASN.1 type names.
--

DLT2811-DataTypes { 1 2 156 2811 1 } DEFINITIONS AUTOMATIC TAGS ::= BEGIN

-- ======================================================================
-- 7.1.1 BOOLEAN
-- ======================================================================

-- PER encoding: constrained integer (0..1), 1 bit
Boolean ::= INTEGER (0..1)

-- ======================================================================
-- 7.1.2 Integer Types
-- ======================================================================

-- PER encoding: constrained integer, 8 bits aligned
Int8  ::= INTEGER (-128..127)

-- PER encoding: constrained integer, 8 bits aligned
Int8U ::= INTEGER (0..255)

-- PER encoding: constrained integer, 16 bits aligned
Int16 ::= INTEGER (-32768..32767)

-- PER encoding: constrained integer, 16 bits aligned
Int16U ::= INTEGER (0..65535)

-- PER encoding: constrained integer, 24 bits aligned
Int24U ::= INTEGER (0..16777215)

-- PER encoding: constrained integer, 32 bits aligned
Int32  ::= INTEGER (-2147483648..2147483647)

-- PER encoding: constrained integer, 32 bits aligned
Int32U ::= INTEGER (0..4294967295)

-- PER encoding: length determinant + content bytes
Int64  ::= INTEGER (-9223372036854775808..9223372036854775807)

-- PER encoding: length determinant + content bytes
Int64U ::= INTEGER (0..18446744073709551615)

-- ======================================================================
-- 7.1.4 Floating-Point Types
-- ======================================================================

Float32 ::= OCTET STRING (SIZE (4))

Float64 ::= OCTET STRING (SIZE (8))

-- ======================================================================
-- 7.1.5 String Types
-- ======================================================================

-- PER encoding: length prefix + 8-bit characters
VisibleString ::= VisibleString
-- VisibleString129::=VisibleString (SIZE (0..129))
-- VisibleString255::=VisibleString (SIZE (0..255))

-- PER encoding: length prefix + UTF-8 bytes
UTF8String ::= UTF8String

-- PER encoding: length prefix + raw bytes
OctetString ::= OCTET STRING

BitString ::= BIT STRING

-- ======================================================================
-- 7.1.6 ENUMERATED
-- ======================================================================

ENUMERATED ::= Int8
-- ENUMERATED ::= Int16 (>128)

-- ======================================================================
-- 7.1.7 CODED ENUM
-- ======================================================================

CODEDENUM ::= BIT STRING (SIZE(0..n))

-- ======================================================================
-- 7.1.8 Packed List
-- ======================================================================

PackedList ::= BIT STRING (SIZE(0..n))

-- ======================================================================
-- 7.2.1 UtcTime
-- ======================================================================

UtcTime ::= OCTET STRING (SIZE(8))

TimeQuality ::= BIT STRING {
    leap-second-known            (0),
    clock-failure                (1),
    clock-not-synchronized       (2)
} (SIZE(8))

-- ======================================================================
-- 7.2.2 BinaryTime / EntryTime
-- ======================================================================

BinaryTime ::= OCTET STRING (SIZE(6))
-- BinaryTime ::= SEQUENCE {                    
--     msOfDay       Int32U,                    -- milliseconds since midnight (0..86399999)
--     daysSince1984 Int16U                     -- days since 1984-01-01
-- }

EntryTime ::= BinaryTime

-- ======================================================================
-- 7.3.1 ObjectName
-- ======================================================================

-- PER encoding: VisibleString with max length 64
ObjectName ::= VisibleString (SIZE(0..64))

-- ======================================================================
-- 7.3.2 ObjectReference
-- ======================================================================

-- Format: LDName/LNName[.Name[....]]
-- PER encoding: VisibleString with max length 129
ObjectReference ::= VisibleString (SIZE(0..129))

-- ======================================================================
-- 7.3.3 SubReference
-- ======================================================================

SubReference ::= VisibleString (SIZE(0..129))

-- ======================================================================
-- 7.3.4 TimeStamp
-- ======================================================================

TimeStamp ::= UtcTime

-- ======================================================================
-- 7.3.5 Dbpos
-- ======================================================================

Dbpos ::= BIT STRING (SIZE(2))

-- ======================================================================
-- 7.3.6 Quality
-- ======================================================================

Quality ::= BIT STRING (SIZE(13))

-- ======================================================================
-- 7.3.7 Tcmd
-- ======================================================================

Tcmd ::= BIT STRING (SIZE(2))

-- ======================================================================
-- 7.3.8 EntryID
-- ======================================================================

EntryID ::= OCTET STRING (SIZE(8))

-- ======================================================================
-- 7.3.9 EntryTime
-- ======================================================================

EntryTime ::= BinaryTime

-- ======================================================================
-- 7.3.10 FileEntry
-- ======================================================================

FileEntry ::= SEQUENCE {
    fileName       [0] IMPLICIT VisibleString129,
    fileSize       [1] IMPLICIT INT32U,
    lastModified   [2] IMPLICIT UtcTime,
    checkSum       [3] IMPLICIT INT32U
}

-- ======================================================================
-- 7.3.11 ServiceError
-- ======================================================================

ServiceError ::= INTEGER {
    no-error                                      (0),
    instance-not-available                        (1),
    instance-in-use                               (2),
    access-violation                              (3),
    access-not-allowed-in-current-state            (4),
    parameter-value-inappropriate                 (5),
    parameter-value-inconsistent                  (6),
    class-not-supported                           (7),
    instance-locked-by-other-client               (8),
    control-must-be-selected                      (9),
    type-conflict                                 (10),
    failed-due-to-communications-constraint       (11),
    failed-due-to-server-constraint               (12)
} (0..12)

-- ======================================================================
-- 7.3.12 PhyComAddr
-- ======================================================================

PhyComAddr ::= SEQUENCE {
    addr        [0] IMPLICIT OCTET STRING (SIZE(6)),
    priority    [1] IMPLICIT Int8U,
    vid         [2] IMPLICIT Int16U,
    appid       [3] IMPLICIT Int16U
}

-- ======================================================================
-- 7.4 FC
-- ======================================================================

FunctionalConstraint ::= VisibleString (SIZE (2))


-- ======================================================================
-- 7.5.1 Control Blocks Attributes
-- ======================================================================

-- ======================================================================
-- 7.5.2 Originator
-- ======================================================================

Originator ::= SEQUENCE {
    orCat        [0] IMPLICIT INTEGER {
        notSupported      (0),
        bayControl        (1),
        stationControl    (2),
        remoteControl     (3),
        automaticBay      (4),
        automaticStation  (5),
        automaticRemote   (6),
        maintenance       (7),
        process           (8)
    } (0..8),
    orIdent      [1] IMPLICIT OCTET STRING (SIZE(0..64))
}

-- ======================================================================
-- 7.5.3 Check
-- ======================================================================

Check ::= BIT STRING {
    syncheck          (0),
    interlock-check   (1)
} (SIZE (2))

-- ======================================================================
-- 7.5.4 AddCause
-- ======================================================================

AddCause ::= INTEGER {
    unknown                              (0),
    not-supported                        (1),
    blocked-by-switching-hierarchy       (2),
    select-failed                        (3),
    invalid-position                     (4),
    position-reached                     (5),
    parameter-change-in-execution        (6),
    step-limit                           (7),
    blocked-by-Mode                      (8),
    blocked-by-process                   (9),
    blocked-by-interlocking              (10),
    blocked-by-syncheck                  (11),
    command-already-in-execution         (12),
    blocked-by-health                    (13),
    one-of-a-control                     (14),
    abortion-by-cancel                   (15),
    time-limit-over                      (16),
    abortion-by-trip                     (17),
    object-not-selected                  (18),
    object-already-selected              (19),
    no-access-authority                  (20),
    ended-with-overshoot                 (21),
    abortion-due-to-deviation            (22),
    abortion-by-communication-loss       (23),
    blocked-by-command                   (24),
    none                                 (25),
    locked-by-other-client               (26),
    inconsistent-parameters              (27)
} (0..27)

-- ======================================================================
-- 7.6.1 Control Blocks
-- ======================================================================

-- SGCB  -> 8.6.6
-- BRCB  -> 8.7.2
-- URCB  -> 8.7.4
-- LCB   -> 8.8.2
-- GoCB  -> 8.9.4
-- MSVCB -> 8.10.2

-- ======================================================================
-- 7.6.2 TriggerConditions
-- ======================================================================

TriggerConditions ::= BIT STRING {
    reserved                    (0),
    data-change                 (1),
    quality-change              (2),
    data-update                 (3),
    integrity                   (4),
    general-interrogation       (5)
} (SIZE(6))

-- ======================================================================
-- 7.6.3 ReasonCode
-- ======================================================================

ReasonCode ::= BIT STRING {
    reserved                    (0),
    data-change                 (1),
    quality-change              (2),
    data-update                 (3),
    integrity                   (4),
    general-interrogation       (5),
    application-trigger         (6)
} (SIZE(7))

-- ======================================================================
-- 7.6.4 RcbOptFlds
-- ======================================================================

RcbOptFlds ::= BIT STRING {
    reserved                    (0),
    sequence-number             (1),
    report-time-stamp           (2),
    reason-for-inclusion        (3),
    data-set-name               (4),
    data-reference              (5),
    buffer-overflow             (6),
    entryID                     (7),
    conf-revision               (8),
    segmentation                (9)
} (SIZE(10))

-- ======================================================================
-- 7.6.5 LcbOptFlds
-- ======================================================================

LcbOptFlds ::= BIT STRING (SIZE(1))

-- ======================================================================
-- 7.6.6 MsvcbOptFlds
-- ======================================================================

MsvcbOptFlds ::= BIT STRING {
    refresh-time                (0),
    reserved                    (1),
    sample-rate                 (2),
    data-set-name               (3),
    security                    (4)
} (SIZE(5))

-- ======================================================================
-- 7.6.7 SmpMod
-- ======================================================================

SmpMod ::= INTEGER {
    samples-per-nominal-period    (0),
    samples-per-second            (1),
    seconds-per-sample            (2)
} (0..2)

-- ======================================================================
-- 7.7 Data (CHOICE of 24 alternatives)
-- ======================================================================

Data ::= CHOICE {
    error              [0] IMPLICIT ServiceError,
    array              [1] IMPLICIT SEQUENCE OF Data,
    structure          [2] IMPLICIT SEQUENCE OF Data,
    boolean            [3] IMPLICIT BOOLEAN,
    int8               [4] IMPLICIT Int8,
    int16              [5] IMPLICIT Int16,
    int32              [6] IMPLICIT Int32,
    int64              [7] IMPLICIT Int64,
    int8u              [8] IMPLICIT Int8U,
    int16u             [9] IMPLICIT Int16U,
    int32u             [10] IMPLICIT Int32U,
    int64u             [11] IMPLICIT Int64U,
    float32            [12] IMPLICIT Float32,
    float64            [13] IMPLICIT Float64,
    bit-string         [14] IMPLICIT BIT STRING,
    octet-string       [15] IMPLICIT OCTET STRING,
    visible-string     [16] IMPLICIT VisibleString,
    unicode-string     [17] IMPLICIT UTF8String,
    utc-time           [18] IMPLICIT UtcTime,
    binary-time        [19] IMPLICIT BinaryTime,
    quality            [20] IMPLICIT Quality,
    dbpos              [21] IMPLICIT Dbpos,
    tcmd               [22] IMPLICIT Tcmd,
    check              [23] IMPLICIT Check
}

-- ======================================================================
-- 7.8 DataDefinition
-- ======================================================================

DataDefinition ::= CHOICE {
    error              [0] IMPLICIT ServiceError,
    array              [1] IMPLICIT SEQUENCE {
        numberOfElement  [1] IMPLICIT Int32,
        elementType      [2] DataDefinition
    },
    structure          [2] IMPLICIT SEQUENCE OF SEQUENCE {
        name             [0] IMPLICIT ObjectName,
        fc               [1] IMPLICIT FunctionalConstraint OPTIONAL,
        type             [2] DataDefinition
    },
    boolean            [3] IMPLICIT NULL,
    int8               [4] IMPLICIT NULL,
    int16              [5] IMPLICIT NULL,
    int32              [6] IMPLICIT NULL,
    int64              [7] IMPLICIT NULL,
    int8u              [8] IMPLICIT NULL,
    int16u             [9] IMPLICIT NULL,
    int32u             [10] IMPLICIT NULL,
    int64u             [11] IMPLICIT NULL,
    float32            [12] IMPLICIT NULL,
    float64            [13] IMPLICIT NULL,
    bit-string         [14] IMPLICIT INTEGER,
    octet-string       [15] IMPLICIT INTEGER,
    visible-string     [16] IMPLICIT INTEGER,
    unicode-string     [17] IMPLICIT INTEGER,
    utc-time           [18] IMPLICIT NULL,
    binary-time        [19] IMPLICIT NULL,
    quality            [20] IMPLICIT NULL,
    dbpos              [21] IMPLICIT NULL,
    tcmd               [22] IMPLICIT NULL,
    check              [23] IMPLICIT NULL
}






--
-- DL/T 2811 Protocol Layer ? APCH / ASDU definitions
--
-- This is the foundation layer for all services.
--

-- ======================================================================
-- APCH ? Application Protocol Control Header (4 bytes)
-- ======================================================================

Apch ::= SEQUENCE {
    cc          ControlCode,
    sc          Int8U,
    fl          Int16U
}

ControlCode ::= SEQUENCE {
    next        BOOLEAN,
    resp        BOOLEAN,
    err         BOOLEAN,
    pi          Int8U
}

-- ======================================================================
-- ASDU ? Application Service Data Unit (base for all services)
-- ======================================================================

-- reqId is the first field in every ASDU
Asdu ::= SEQUENCE {
    reqId       Int16U
}

-- ======================================================================
-- APDU ? Complete application-layer frame
-- ======================================================================

Apdu ::= SEQUENCE {
    apch        Apch,
    asdu        OCTET STRING (SIZE(0..65531))
}

--
-- DL/T 2811 Association Services ? Associate / Release / Abort
--

-- ======================================================================
-- 8.2.1 Associate (Service Code 0x01)
-- ======================================================================

-- Request: serverAccessPointReference + authenticationParameter
-- Response+: associationId + serviceError + authenticationParameter
-- Response-: serviceError

VisibleString129 ::= VisibleString (SIZE(0..129))

Associate-RequestPDU ::= SEQUENCE {
    serverAccessPointReference    [0] IMPLICIT VisibleString129 OPTIONAL,
    authenticationParameter       [1] IMPLICIT SEQUENCE {
        signatureCertificate        [0] IMPLICIT OCTET STRING,
        signedTime                  [1] IMPLICIT UtcTime,
        signedValue                 [2] IMPLICIT OCTET STRING
    } OPTIONAL
}

Associate-ResponsePDU ::= SEQUENCE {
    associationId                  [0] IMPLICIT OCTET STRING (SIZE (0..64)),
    serviceError                   [1] IMPLICIT ServiceError,
    authenticationParameter        [2] IMPLICIT SEQUENCE {
        signatureCertificate        [0] IMPLICIT OCTET STRING,
        signedTime                  [1] IMPLICIT UtcTime,
        signedValue                 [2] IMPLICIT OCTET STRING
    } OPTIONAL
}

Associate-ErrorPDU ::= ServiceError

-- ======================================================================
-- 8.2.2 Release (Service Code 0x02)
-- ======================================================================

-- Release-RequestPDU: associationId
-- Release-ResponsePDU: associationId + serviceError
-- Release-ErrorPDU: serviceError

Release-RequestPDU ::= SEQUENCE {
    associationId    [0] IMPLICIT OCTET STRING (SIZE (0..64))
}

Release-ResponsePDU ::= SEQUENCE {
    associationId    [0] IMPLICIT OCTET STRING (SIZE (0..64)),
    serviceError     [1] IMPLICIT ServiceError
}

Release-ErrorPDU ::= ServiceError

-- ======================================================================
-- 8.2.3 Abort (Service Code 0x03)
-- ======================================================================

Abort-RequestPDU ::= SEQUENCE {
    associationId    [0] IMPLICIT OCTET STRING (SIZE (0..64)),
    reason           [1] IMPLICIT INTEGER {
        other                  (0),
        unrecognized-service   (1),
        invalid-reqID          (2),
        invalid-argument       (3),
        invalid-result         (4),
        max-serv-outstanding-exceeded (5)
    } (0..5)
}

-- ======================================================================
-- 8.3.1 GetServerDirectory (Service Code 0x51)
-- ======================================================================

GetServerDirectory-RequestPDU ::= SEQUENCE {
    objectClass      [0] IMPLICIT INTEGER {
        reserved        (0),
        logical-device  (1),
        file-system     (2)
    } (0..2),
    referenceAfter   [1] IMPLICIT ObjectReference OPTIONAL
}

GetServerDirectory-ResponsePDU ::= SEQUENCE {
    reference        [0] IMPLICIT SEQUENCE OF ObjectReference,
    moreFollows      [1] IMPLICIT BOOLEAN DEFAULT TRUE
}

GetServerDirectory-ErrorPDU ::= ServiceError

-- ======================================================================
-- 8.3.2 GetLogicalDeviceDirectory (Service Code 0x52)
-- ======================================================================

GetLogicalDeviceDirectory-RequestPDU ::= SEQUENCE {
    ldName            [0] IMPLICIT ObjectName OPTIONAL,
    referenceAfter    [1] IMPLICIT ObjectReference OPTIONAL
}

GetLogicalDeviceDirectory-ResponsePDU ::= SEQUENCE {
    lnReference       [0] IMPLICIT SEQUENCE OF SubReference,
    moreFollows       [1] IMPLICIT BOOLEAN DEFAULT TRUE
}

GetLogicalDeviceDirectory-ErrorPDU ::= ServiceError

-- ======================================================================
-- 8.3.3 GetLogicalNodeDirectory (Service Code 0x53)
-- ======================================================================

ACSIClass ::= INTEGER {
    reserved       (0),
    data-object    (1),
    data-set       (2),
    brcb           (3),
    urcb           (4),
    lcb            (5),
    log            (6),
    sgecb          (7),
    gocb           (8),
    msvcb          (10)
} (0..10)

GetLogicalNodeDirectory-RequestPDU ::= SEQUENCE {
    reference       [0] IMPLICIT CHOICE {
        ldName        [0] IMPLICIT ObjectName,
        lnReference   [1] IMPLICIT ObjectReference
    },
    acsiClass       [1] IMPLICIT ACSIClass,
    referenceAfter  [2] IMPLICIT ObjectReference OPTIONAL
}

GetLogicalNodeDirectory-ResponsePDU ::= SEQUENCE {
    reference       [0] IMPLICIT SEQUENCE OF SubReference,
    moreFollows     [1] IMPLICIT BOOLEAN DEFAULT TRUE
}

GetLogicalNodeDirectory-ErrorPDU ::= ServiceError

-- ======================================================================
-- 8.3.4 GetAllDataValues (Service Code 0x54)
-- ======================================================================

GetAllDataValues-RequestPDU ::= SEQUENCE {
    reference        [0] IMPLICIT CHOICE {
        ldName         [0] IMPLICIT ObjectName,
        lnReference    [1] IMPLICIT ObjectReference
    },
    fc               [1] IMPLICIT FunctionalConstraint OPTIONAL,
    referenceAfter   [2] IMPLICIT ObjectReference OPTIONAL
}

GetAllDataValues-ResponsePDU ::= SEQUENCE {
    data             [0] IMPLICIT SEQUENCE OF SEQUENCE {
        reference     [0] IMPLICIT SubReference,
        value         [1] IMPLICIT Data
    },
    moreFollows      [1] IMPLICIT BOOLEAN DEFAULT TRUE
}

GetAllDataValues-ErrorPDU ::= ServiceError

-- ======================================================================
-- 8.3.5 GetAllDataDefinition (Service Code 0x55)
-- ======================================================================

GetAllDataDefinition-RequestPDU ::= SEQUENCE {
    reference        [0] IMPLICIT CHOICE {
        ldName         [0] IMPLICIT ObjectName,
        lnReference    [1] IMPLICIT ObjectReference
    },
    fc               [1] IMPLICIT FunctionalConstraint OPTIONAL,
    referenceAfter   [2] IMPLICIT ObjectReference OPTIONAL
}

GetAllDataDefinition-ResponsePDU ::= SEQUENCE {
    data             [0] IMPLICIT SEQUENCE OF SEQUENCE {
        reference     [0] IMPLICIT SubReference,
        cdcType       [1] IMPLICIT VisibleString OPTIONAL,
        definition    [2] IMPLICIT DataDefinition
    },
    moreFollows      [1] IMPLICIT BOOLEAN DEFAULT TRUE
}

GetAllDataDefinition-ErrorPDU ::= ServiceError

-- ======================================================================
-- 8.3.6 GetAllCBValues (Service Code 0x56)
-- ======================================================================


GetAllCBValues-RequestPDU ::= SEQUENCE {
    reference        [0] IMPLICIT CHOICE {
        ldName         [0] IMPLICIT ObjectName,
        lnReference    [1] IMPLICIT ObjectReference
    },
    acsiClass        [1] IMPLICIT ACSIClass,
    referenceAfter   [2] IMPLICIT ObjectReference OPTIONAL
}

GetAllCBValues-ResponsePDU ::= SEQUENCE {
    cbValue          [0] IMPLICIT SEQUENCE OF SEQUENCE {
        reference     [0] IMPLICIT SubReference,
        value         [1] IMPLICIT CHOICE {
            brcb        [0] IMPLICIT BRCB,
            urcb        [1] IMPLICIT URCB,
            lcb         [2] IMPLICIT LCB,
            sgecb       [3] IMPLICIT SGECB,
            gocb        [4] IMPLICIT GOCB,
            msvcb       [5] IMPLICIT MSVCB
        }
    },
    moreFollows      [1] IMPLICIT BOOLEAN DEFAULT TRUE
}

GetAllCBValues-ErrorPDU ::= ServiceError

-- ======================================================================
-- 8.4.1 GetDataValues (Service Code 0x11)
-- ======================================================================

GetDataValues-RequestPDU ::= SEQUENCE {
    data             [0] IMPLICIT SEQUENCE OF SEQUENCE {
        reference     [0] IMPLICIT ObjectReference,
        fc            [1] IMPLICIT FunctionalConstraint OPTIONAL
    }
}

GetDataValues-ResponsePDU ::= SEQUENCE {
    value            [0] IMPLICIT SEQUENCE OF Data,
    moreFollows      [1] IMPLICIT BOOLEAN DEFAULT TRUE
}

GetDataValues-ErrorPDU ::= ServiceError

-- ======================================================================
-- 8.4.2 SetDataValues (Service Code 0x12)
-- ======================================================================

SetDataValues-RequestPDU ::= SEQUENCE {
    data             [0] IMPLICIT SEQUENCE OF SEQUENCE {
        reference     [0] IMPLICIT ObjectReference,
        fc            [1] IMPLICIT FunctionalConstraint OPTIONAL,
        value         [2] IMPLICIT Data
    }
}

SetDataValues-ResponsePDU ::= NULL

SetDataValues-ErrorPDU ::= SEQUENCE {
    result           [0] IMPLICIT SEQUENCE OF ServiceError
}

-- ======================================================================
-- 8.4.3 GetDataDirectory (Service Code 0x14)
-- ======================================================================


GetDataDirectory-RequestPDU ::= SEQUENCE {
    dataReference    [0] IMPLICIT ObjectReference,
    referenceAfter   [1] IMPLICIT ObjectReference OPTIONAL
}

GetDataDirectory-ResponsePDU ::= SEQUENCE {
    dataAttribute    [0] IMPLICIT SEQUENCE OF SEQUENCE {
        reference     [0] IMPLICIT SubReference,
        fc            [1] IMPLICIT FunctionalConstraint OPTIONAL
    },
    moreFollows      [1] IMPLICIT BOOLEAN DEFAULT TRUE
}

GetDataDirectory-ErrorPDU ::= ServiceError


-- ======================================================================
-- 8.4.4 GetDataDefinition (Service Code 0x13)
-- ======================================================================

GetDataDefinition-RequestPDU ::= SEQUENCE {
    data             [0] IMPLICIT SEQUENCE OF SEQUENCE {
        reference     [0] IMPLICIT ObjectReference,
        fc            [1] IMPLICIT FunctionalConstraint OPTIONAL
    }
}

GetDataDefinition-ResponsePDU ::= SEQUENCE {
    data             [0] IMPLICIT SEQUENCE OF SEQUENCE {
        cdcType       [0] IMPLICIT VisibleString OPTIONAL,
        definition    [1] IMPLICIT DataDefinition
    },
    moreFollows      [1] IMPLICIT BOOLEAN DEFAULT TRUE
}

GetDataDefinition-ErrorPDU ::= ServiceError

-- ======================================================================
-- 6.5.1 GetDataSetValues (Service Code 0x44)
-- ======================================================================

GetDataSetValues-RequestPDU ::= SEQUENCE {
    datasetReference    [0] IMPLICIT ObjectReference,
    referenceAfter      [1] IMPLICIT ObjectReference OPTIONAL
}

GetDataSetValues-ResponsePDU ::= SEQUENCE {
    value               [0] IMPLICIT SEQUENCE OF Data,
    moreFollows         [1] IMPLICIT BOOLEAN DEFAULT TRUE
}

GetDataSetValues-ErrorPDU ::= ServiceError

-- ======================================================================
-- 8.5.2 SetDataSetValues (Service Code 0x45)
-- ======================================================================

SetDataSetValues-RequestPDU ::= SEQUENCE {
    datasetReference    [0] IMPLICIT ObjectReference,
    referenceAfter      [1] IMPLICIT ObjectReference OPTIONAL,
    value               [2] IMPLICIT SEQUENCE OF Data
}

SetDataSetValues-ResponsePDU ::= NULL

SetDataSetValues-ErrorPDU ::= SEQUENCE {
    result              [0] IMPLICIT SEQUENCE OF ServiceError
}

-- ======================================================================
-- 8.5.3 CreateDataSet (Service Code 0x41)
-- ======================================================================

CreateDataSet-RequestPDU ::= SEQUENCE {
    datasetReference    [0] IMPLICIT ObjectReference,
    referenceAfter      [1] IMPLICIT ObjectReference OPTIONAL,
    memberData          [2] IMPLICIT SEQUENCE OF SEQUENCE {
        reference       [0] IMPLICIT ObjectReference,
        fc              [1] IMPLICIT FunctionalConstraint
    }
}

CreateDataSet-ResponsePDU ::= NULL

CreateDataSet-ErrorPDU ::= ServiceError

-- ======================================================================
-- 8.5.4 DeleteDataSet (Service Code 0x42)
-- ======================================================================

DeleteDataSet-RequestPDU ::= SEQUENCE {
    datasetReference    [0] IMPLICIT ObjectReference
}

DeleteDataSet-ResponsePDU ::= NULL

DeleteDataSet-ErrorPDU ::= ServiceError

-- ======================================================================
-- 8.5.5 GetDataSetDirectory (Service Code 0x43)
-- ======================================================================

GetDataSetDirectory-RequestPDU ::= SEQUENCE {
    datasetReference    [0] IMPLICIT ObjectReference,
    referenceAfter      [1] IMPLICIT ObjectReference OPTIONAL
}

GetDataSetDirectory-ResponsePDU ::= SEQUENCE {
    memberData          [0] IMPLICIT SEQUENCE OF SEQUENCE {
        reference       [0] IMPLICIT ObjectReference,
        fc              [1] IMPLICIT FunctionalConstraint
    },
    moreFollows         [1] IMPLICIT BOOLEAN DEFAULT TRUE
}

GetDataSetDirectory-ErrorPDU ::= ServiceError

-- ======================================================================
-- 8.6.1 SelectActiveSG (Service Code 0x62)
-- ======================================================================

SelectActiveSG-RequestPDU ::= SEQUENCE {
    sgcbReference       [0] IMPLICIT ObjectReference,
    settingGroupNumber  [1] IMPLICIT INT8U
}

SelectActiveSG-ResponsePDU ::= NULL

SelectActiveSG-ErrorPDU ::= ServiceError

-- ======================================================================
-- 8.6.2 SelectEditSG (Service Code 0x63)
-- ======================================================================

SelectEditSG-RequestPDU ::= SEQUENCE {
    sgcbReference       [0] IMPLICIT ObjectReference,
    settingGroupNumber  [1] IMPLICIT INT8U
}

SelectEditSG-ResponsePDU ::= NULL

SelectEditSG-ErrorPDU ::= ServiceError

-- ======================================================================
-- 8.6.3 SetEditSGValue (Service Code 0x66)
-- ======================================================================

SetEditSGValue-RequestPDU ::= SEQUENCE {
    data    [0] IMPLICIT SEQUENCE OF SEQUENCE {
        reference   [0] IMPLICIT ObjectReference,
        value       [2] IMPLICIT Data
    }
}

SetEditSGValue-ResponsePDU ::= NULL

SetEditSGValue-ErrorPDU ::= SEQUENCE {
    result  [0] IMPLICIT SEQUENCE OF ServiceError
}

-- ======================================================================
-- 8.6.4 ConfirmEditSGValues (Service Code 0x64)
-- ======================================================================

ConfirmEditSGValues-RequestPDU ::= SEQUENCE {
    sgcbReference       [0] IMPLICIT ObjectReference
}

ConfirmEditSGValues-ResponsePDU ::= NULL

ConfirmEditSGValues-ErrorPDU ::= ServiceError

-- ======================================================================
-- 8.6.5 GetEditSGValue (Service Code 0x65)
-- ======================================================================

GetEditSGValue-RequestPDU ::= SEQUENCE {
    data    [0] IMPLICIT SEQUENCE OF SEQUENCE {
        reference   [0] IMPLICIT ObjectReference,
        fc          [1] IMPLICIT FunctionalConstraint
    }
}

GetEditSGValue-ResponsePDU ::= SEQUENCE {
    value           [0] IMPLICIT SEQUENCE OF Data,
    moreFollows     [1] IMPLICIT BOOLEAN DEFAULT TRUE
}

GetEditSGValue-ErrorPDU ::= ServiceError

-- ======================================================================
-- 8.6.6 GetSGCBValues (Service Code 0x61)
-- ======================================================================

SGCB ::= SEQUENCE {
    numOfSG       [1] IMPLICIT INT8U,
    actSG         [2] IMPLICIT INT8U,
    editSG        [3] IMPLICIT INT8U,
    tActEdt       [4] IMPLICIT TimeStamp,
    resvTms       [5] IMPLICIT INT16U OPTIONAL
}

GetSGCBValues-RequestPDU ::= SEQUENCE {
    sgcbReference  [0] IMPLICIT SEQUENCE OF ObjectReference
}

GetSGCBValues-ResponsePDU ::= SEQUENCE {
    sgscb          [0] IMPLICIT SEQUENCE OF CHOICE {
        error       [0] IMPLICIT ServiceError,
        value       [1] IMPLICIT SGCB
    },
    moreFollows    [1] IMPLICIT BOOLEAN DEFAULT TRUE
}

GetSGCBValues-ErrorPDU ::= ServiceError

-- ======================================================================
-- 8.7.1 Report (Service Code 0x35, unconfirmed)
-- ======================================================================

ReportPDU ::= SEQUENCE {
    rptID           [0] IMPLICIT VisibleString129,
    optFlds         [1] IMPLICIT RCBOptFlds,
    sqNum           [2] IMPLICIT INT16U OPTIONAL,
    subSeqNum       [3] IMPLICIT INT16U OPTIONAL,
    moreSegmentsFollow [4] IMPLICIT BOOLEAN OPTIONAL,
    dataSet         [5] IMPLICIT ObjectReference OPTIONAL,
    bufOvfl         [6] IMPLICIT BOOLEAN OPTIONAL,
    confRev         [7] IMPLICIT INT32U OPTIONAL,
    entry           [8] IMPLICIT SEQUENCE {
        timeOfEntry     [0] IMPLICIT EntryTime OPTIONAL,
        entryID         [1] IMPLICIT EntryID OPTIONAL,
        entryData       [2] IMPLICIT SEQUENCE OF SEQUENCE {
            reference   [0] IMPLICIT ObjectReference OPTIONAL,
            fc          [1] IMPLICIT FunctionalConstraint OPTIONAL,
            id          [2] IMPLICIT INT16U,
            value       [3] IMPLICIT Data,
            reason      [4] IMPLICIT ReasonCode OPTIONAL
        }
    }
}

-- ======================================================================
-- 8.7.2 GetBRCBValues (Service Code 0x31)
-- ======================================================================

BRCB ::= SEQUENCE {
    rptID           [1] IMPLICIT VisibleString129,
    rptEna          [2] IMPLICIT BOOLEAN,
    datSet          [3] IMPLICIT ObjectReference,
    confRev         [4] IMPLICIT INT32U,
    optFlds         [5] IMPLICIT RCBOptFlds,
    bufTm           [6] IMPLICIT INT32U,
    sqNum           [7] IMPLICIT INT16U,
    trgOps          [8] IMPLICIT TriggerConditions,
    intgPd          [9] IMPLICIT INT32U,
    gi              [10] IMPLICIT BOOLEAN,
    purgeBuf        [11] IMPLICIT BOOLEAN,
    entryID         [12] IMPLICIT EntryID,
    timeOfEntry     [13] IMPLICIT EntryTime,
    resvTms         [14] IMPLICIT INT16 OPTIONAL,
    owner           [15] IMPLICIT OCTET STRING (SIZE (0..64)) OPTIONAL
}

GetBRCBValues-RequestPDU ::= SEQUENCE {
    reference       [0] IMPLICIT SEQUENCE OF ObjectReference
}

GetBRCBValues-ResponsePDU ::= SEQUENCE {
    brcb            [0] IMPLICIT SEQUENCE OF CHOICE {
        error       [0] IMPLICIT ServiceError,
        value       [1] IMPLICIT BRCB
    },
    moreFollows     [1] IMPLICIT BOOLEAN DEFAULT TRUE
}

GetBRCBValues-ErrorPDU ::= ServiceError

-- ======================================================================
-- 8.7.3 SetBRCBValues (Service Code 0x32)
-- ======================================================================

SetBRCBValues-RequestPDU ::= SEQUENCE {
    brcb            [0] IMPLICIT SEQUENCE OF SEQUENCE {
        reference   [0] IMPLICIT ObjectReference,
        rptID       [1] IMPLICIT VisibleString129 OPTIONAL,
        rptEna      [2] IMPLICIT BOOLEAN OPTIONAL,
        datSet      [3] IMPLICIT ObjectReference OPTIONAL,
        optFlds     [5] IMPLICIT RCBOptFlds OPTIONAL,
        bufTm       [6] IMPLICIT INT32U OPTIONAL,
        trgOps      [8] IMPLICIT TriggerConditions OPTIONAL,
        intgPd      [9] IMPLICIT INT32U OPTIONAL,
        gi          [10] IMPLICIT BOOLEAN OPTIONAL,
        purgeBuf    [11] IMPLICIT BOOLEAN OPTIONAL,
        entryID     [12] IMPLICIT EntryID OPTIONAL,
        resvTms     [13] IMPLICIT INT16 OPTIONAL
    }
}

SetBRCBValues-ResponsePDU ::= NULL

SetBRCBValues-ErrorPDU ::= SEQUENCE {
    result          [0] IMPLICIT SEQUENCE OF SEQUENCE {
        error       [0] IMPLICIT ServiceError OPTIONAL,
        rptID       [1] IMPLICIT ServiceError OPTIONAL,
        rptEna      [2] IMPLICIT ServiceError OPTIONAL,
        datSet      [3] IMPLICIT ServiceError OPTIONAL,
        optFlds     [5] IMPLICIT ServiceError OPTIONAL,
        bufTm       [6] IMPLICIT ServiceError OPTIONAL,
        trgOps      [8] IMPLICIT ServiceError OPTIONAL,
        intgPd      [9] IMPLICIT ServiceError OPTIONAL,
        gi          [10] IMPLICIT ServiceError OPTIONAL,
        purgeBuf    [11] IMPLICIT ServiceError OPTIONAL,
        entryID     [12] IMPLICIT ServiceError OPTIONAL,
        resvTms     [14] IMPLICIT ServiceError OPTIONAL
    }
}

-- ======================================================================
-- 8.7.4 GetURCBValues (Service Code 0x33)
-- ======================================================================

URCB ::= SEQUENCE {
    rptID           [1] IMPLICIT VisibleString129,
    rptEna          [2] IMPLICIT BOOLEAN,
    datSet          [3] IMPLICIT ObjectReference,
    confRev         [4] IMPLICIT INT32U,
    optFlds         [5] IMPLICIT RCBOptFlds,
    bufTm           [6] IMPLICIT INT32U,
    sqNum           [7] IMPLICIT INT16U,
    trgOps          [8] IMPLICIT TriggerConditions,
    intgPd          [9] IMPLICIT INT32U,
    gi              [10] IMPLICIT BOOLEAN,
    resv            [14] IMPLICIT BOOLEAN,
    owner           [15] IMPLICIT OCTET STRING (SIZE (0..64)) OPTIONAL
}

GetURCBValues-RequestPDU ::= SEQUENCE {
    reference       [0] IMPLICIT SEQUENCE OF ObjectReference
}

GetURCBValues-ResponsePDU ::= SEQUENCE {
    urcb            [0] IMPLICIT SEQUENCE OF CHOICE {
        error       [0] IMPLICIT ServiceError,
        value       [1] IMPLICIT URCB
    },
    moreFollows     [1] IMPLICIT BOOLEAN DEFAULT TRUE
}

GetURCBValues-ErrorPDU ::= ServiceError

-- ======================================================================
-- 8.7.5 SetURCBValues (Service Code 0x34)
-- ======================================================================

SetURCBValues-RequestPDU ::= SEQUENCE {
    urcb            [0] IMPLICIT SEQUENCE OF SEQUENCE {
        reference   [0] IMPLICIT ObjectReference,
        rptID       [1] IMPLICIT VisibleString129 OPTIONAL,
        rptEna      [2] IMPLICIT BOOLEAN OPTIONAL,
        datSet      [3] IMPLICIT ObjectReference OPTIONAL,
        optFlds     [5] IMPLICIT RCBOptFlds OPTIONAL,
        bufTm       [6] IMPLICIT INT32U OPTIONAL,
        trgOps      [8] IMPLICIT TriggerConditions OPTIONAL,
        intgPd      [9] IMPLICIT INT32U OPTIONAL,
        gi          [10] IMPLICIT BOOLEAN OPTIONAL,
        resv        [13] IMPLICIT BOOLEAN OPTIONAL
    }
}

SetURCBValues-ResponsePDU ::= NULL

SetURCBValues-ErrorPDU ::= SEQUENCE {
    result          [0] IMPLICIT SEQUENCE OF SEQUENCE {
        error       [0] IMPLICIT ServiceError OPTIONAL,
        rptID       [1] IMPLICIT ServiceError OPTIONAL,
        rptEna      [2] IMPLICIT ServiceError OPTIONAL,
        datSet      [3] IMPLICIT ServiceError OPTIONAL,
        optFlds     [5] IMPLICIT ServiceError OPTIONAL,
        bufTm       [6] IMPLICIT ServiceError OPTIONAL,
        trgOps      [8] IMPLICIT ServiceError OPTIONAL,
        intgPd      [9] IMPLICIT ServiceError OPTIONAL,
        gi          [10] IMPLICIT ServiceError OPTIONAL,
        resv        [13] IMPLICIT ServiceError OPTIONAL
    }
}

-- ======================================================================
-- 8.8.1 LogEntry 
-- ======================================================================

LogEntry ::= SEQUENCE {
    timeOfEntry     [0] IMPLICIT EntryTime,
    entryID         [1] IMPLICIT EntryID,
    entryData       [2] IMPLICIT SEQUENCE OF SEQUENCE {
        reference   [0] IMPLICIT ObjectReference,
        fc          [1] IMPLICIT FunctionalConstraint,
        value       [2] IMPLICIT Data,
        reason      [3] IMPLICIT ReasonCode
    }
}

-- ======================================================================
-- 8.8.2 GetLCBValues (Service Code 0x67)
-- ======================================================================

LCB ::= SEQUENCE {
    logEna          [1] IMPLICIT BOOLEAN,
    datSet          [2] IMPLICIT ObjectReference,
    trgOps          [3] IMPLICIT TriggerConditions,
    intgPd          [4] IMPLICIT INT32U,
    logRef          [5] IMPLICIT ObjectReference,
    optFlds         [6] IMPLICIT LCBOptFlds OPTIONAL,
    bufTm           [7] IMPLICIT INT32U OPTIONAL
}

GetLCBValues-RequestPDU ::= SEQUENCE {
    reference       [0] IMPLICIT SEQUENCE OF ObjectReference
}

GetLCBValues-ResponsePDU ::= SEQUENCE {
    lcb             [0] IMPLICIT SEQUENCE OF CHOICE {
        error       [0] IMPLICIT ServiceError,
        value       [1] IMPLICIT LCB
    },
    moreFollows     [1] IMPLICIT BOOLEAN DEFAULT TRUE
}

GetLCBValues-ErrorPDU ::= ServiceError

-- ======================================================================
-- 8.8.3 SetLCBValues (Service Code 0x68)
-- ======================================================================

SetLCBValues-RequestPDU ::= SEQUENCE {
    lcb             [0] IMPLICIT SEQUENCE OF SEQUENCE {
        reference   [0] IMPLICIT ObjectReference,
        logEna      [1] IMPLICIT BOOLEAN OPTIONAL,
        datSet      [2] IMPLICIT ObjectReference OPTIONAL,
        trgOps      [3] IMPLICIT TriggerConditions OPTIONAL,
        intgPd      [4] IMPLICIT INT32U OPTIONAL,
        logRef      [5] IMPLICIT ObjectReference OPTIONAL,
        optFlds     [6] IMPLICIT LCBOptFlds OPTIONAL,
        bufTm       [7] IMPLICIT INT32U OPTIONAL
    }
}

SetLCBValues-ResponsePDU ::= NULL

SetLCBValues-ErrorPDU ::= SEQUENCE {
    result          [0] IMPLICIT SEQUENCE OF SEQUENCE {
        error       [0] IMPLICIT ServiceError OPTIONAL,
        logEna      [1] IMPLICIT ServiceError OPTIONAL,
        datSet      [2] IMPLICIT ServiceError OPTIONAL,
        trgOps      [3] IMPLICIT ServiceError OPTIONAL,
        intgPd      [4] IMPLICIT ServiceError OPTIONAL,
        logRef      [5] IMPLICIT ServiceError OPTIONAL,
        optFlds     [6] IMPLICIT ServiceError OPTIONAL,
        bufTm       [7] IMPLICIT ServiceError OPTIONAL
    }
}

-- ======================================================================
-- 8.8.4 QueryLogByTime (Service Code 0x6B)
-- ======================================================================

QueryLogByTime-RequestPDU ::= SEQUENCE {
    logReference    [0] IMPLICIT ObjectReference,
    startTime       [1] IMPLICIT EntryTime OPTIONAL,
    stopTime        [2] IMPLICIT EntryTime OPTIONAL,
    entryAfter      [3] IMPLICIT EntryID OPTIONAL
}

QueryLogByTime-ResponsePDU ::= SEQUENCE {
    logEntry        [0] IMPLICIT SEQUENCE OF LogEntry,
    moreFollows     [1] IMPLICIT BOOLEAN DEFAULT TRUE
}

QueryLogByTime-ErrorPDU ::= ServiceError

-- ======================================================================
-- 8.8.5 QueryLogAfter (Service Code 0x6A)
-- ======================================================================

QueryLogAfter-RequestPDU ::= SEQUENCE {
    logReference    [0] IMPLICIT ObjectReference,
    startTime       [1] IMPLICIT EntryTime OPTIONAL,
    entry           [2] IMPLICIT EntryID
}

QueryLogAfter-ResponsePDU ::= SEQUENCE {
    logEntry        [0] IMPLICIT SEQUENCE OF LogEntry,
    moreFollows     [1] IMPLICIT BOOLEAN DEFAULT TRUE
}

QueryLogAfter-ErrorPDU ::= ServiceError

-- ======================================================================
-- 8.8.6 GetLogStatusValues (Service Code 0x69)
-- ======================================================================

GetLogStatusValues-RequestPDU ::= SEQUENCE {
    logReference    [0] IMPLICIT SEQUENCE OF ObjectReference
}

GetLogStatusValues-ResponsePDU ::= SEQUENCE {
    log             [0] IMPLICIT SEQUENCE OF CHOICE {
        error       [0] IMPLICIT ServiceError,
        value       [1] IMPLICIT SEQUENCE {
            oldEntrTm   [0] IMPLICIT EntryTime,
            newEntrTm   [1] IMPLICIT EntryTime,
            oldEntr     [2] IMPLICIT EntryID,
            newEntr     [3] IMPLICIT EntryID
        }
    },
    moreFollows     [1] IMPLICIT BOOLEAN DEFAULT TRUE
}

GetLogStatusValues-ErrorPDU ::= ServiceError

-- ======================================================================
-- 8.9.1 SendGooseMessage (Service Code 0x84, unconfirmed)
-- ======================================================================

SendGOOSEMessage-PDU ::= SEQUENCE {
    goID            [0] IMPLICIT VisibleString129,
    datSet          [1] IMPLICIT ObjectReference OPTIONAL,
    goRef           [2] IMPLICIT ObjectReference OPTIONAL,
    t               [3] IMPLICIT TimeStamp,
    stNum           [4] IMPLICIT INT32U,
    sqNum           [5] IMPLICIT INT32U,
    simulation      [6] IMPLICIT BOOLEAN,
    confRev         [7] IMPLICIT INT32U,
    ndsCom          [8] IMPLICIT BOOLEAN,
    data            [9] IMPLICIT SEQUENCE OF Data
}

-- ======================================================================
-- 8.9.2 GetGoReference (Service Code 0x81)
-- ======================================================================

GetGoReference-RequestPDU ::= SEQUENCE {
    gocbReference   [0] IMPLICIT ObjectReference,
    memberOfs       [1] IMPLICIT SEQUENCE OF INT16U
}

GetGoReference-ResponsePDU ::= SEQUENCE {
    gocbReference   [0] IMPLICIT ObjectReference,
    confRev         [1] IMPLICIT INT32U,
    datSet          [2] IMPLICIT ObjectReference,
    memberData      [3] IMPLICIT SEQUENCE OF SEQUENCE {
        reference   [0] IMPLICIT ObjectReference,
        fc          [1] IMPLICIT FunctionalConstraint
    }
}

GetGoReference-ErrorPDU ::= ServiceError

-- ======================================================================
-- 8.9.3 GetGooseElementNumber (Service Code 0x85)
-- ======================================================================

GetGOOSEElementNumber-RequestPDU ::= SEQUENCE {
    gocbReference   [0] IMPLICIT ObjectReference,
    memberData      [1] IMPLICIT SEQUENCE OF SEQUENCE {
        reference   [0] IMPLICIT ObjectReference,
        fc          [1] IMPLICIT FunctionalConstraint
    }
}

GetGOOSEElementNumber-ResponsePDU ::= SEQUENCE {
    gocbReference   [0] IMPLICIT ObjectReference,
    confRev         [1] IMPLICIT INT32U,
    datSet          [2] IMPLICIT ObjectReference,
    memberOffset    [3] IMPLICIT SEQUENCE OF INT16U
}

GetGOOSEElementNumber-ErrorPDU ::= ServiceError

-- ======================================================================
-- 8.9.4 GetGoCBValues (Service Code 0x82)
-- ======================================================================

GoCB ::= SEQUENCE {
    goEna           [1] IMPLICIT BOOLEAN,
    goID            [2] IMPLICIT VisibleString129,
    datSet          [3] IMPLICIT ObjectReference,
    confRev         [4] IMPLICIT INT32U,
    ndsCom          [5] IMPLICIT BOOLEAN,
    dstAddress      [6] IMPLICIT PHYCOMADDR OPTIONAL
}

GetGoCbValues-RequestPDU ::= SEQUENCE {
    reference       [0] IMPLICIT SEQUENCE OF ObjectReference
}

GetGoCbValues-ResponsePDU ::= SEQUENCE {
    gocb            [0] IMPLICIT SEQUENCE OF CHOICE {
        error       [0] IMPLICIT ServiceError,
        value       [1] IMPLICIT GoCB
    },
    moreFollows     [1] IMPLICIT BOOLEAN DEFAULT TRUE
}

GetGoCbValues-ErrorPDU ::= ServiceError

-- ======================================================================
-- 8.9.5 SetGoCBValues (Service Code 0x83)
-- ======================================================================

SetGoCBValues-RequestPDU ::= SEQUENCE {
    gocb            [0] IMPLICIT SEQUENCE OF SEQUENCE {
        reference   [0] IMPLICIT ObjectReference,
        goEna       [1] IMPLICIT BOOLEAN OPTIONAL,
        goID        [2] IMPLICIT VisibleString129 OPTIONAL,
        datSet      [3] IMPLICIT ObjectReference OPTIONAL
    }
}

SetGoCBValues-ResponsePDU ::= NULL

SetGoCBValues-ErrorPDU ::= SEQUENCE {
    result          [0] IMPLICIT SEQUENCE OF SEQUENCE {
        error       [0] IMPLICIT ServiceError OPTIONAL,
        goEna       [1] IMPLICIT ServiceError OPTIONAL,
        goID        [2] IMPLICIT ServiceError OPTIONAL,
        datSet      [3] IMPLICIT ServiceError OPTIONAL
    }
}

-- ======================================================================
-- 8.10.1 SendMSVMessage (Service Code 0x88, unconfirmed)
-- ======================================================================

SendMSVMessage-PDU ::= SEQUENCE {
    msvID           [0] IMPLICIT VisibleString129,
    datSet          [1] IMPLICIT ObjectReference OPTIONAL,
    smpCnt          [2] IMPLICIT INT16U,
    confRev         [3] IMPLICIT INT32U,
    refTm           [4] IMPLICIT TimeStamp OPTIONAL,
    smpSynch        [5] IMPLICIT INT8U,
    smpRate         [6] IMPLICIT INT16U OPTIONAL,
    simulation      [7] IMPLICIT BOOLEAN,
    sample          [8] IMPLICIT SEQUENCE OF Data,
    smpMod          [9] IMPLICIT SmpMod OPTIONAL
}

-- ======================================================================
-- 8.10.2 GetMSVCBValues (Service Code 0x86)
-- ======================================================================

MSVCB ::= SEQUENCE {
    svEna           [1] IMPLICIT BOOLEAN,
    msvID           [2] IMPLICIT VisibleString129,
    datSet          [3] IMPLICIT ObjectReference,
    confRev         [4] IMPLICIT INT32U,
    smpMod          [5] IMPLICIT SmpMod OPTIONAL,
    smpRate         [6] IMPLICIT INT16U,
    optFlds         [7] IMPLICIT MSVCBOptFlds,
    dstAddress      [8] IMPLICIT PHYCOMADDR OPTIONAL
}

GetMSVCBValues-RequestPDU ::= SEQUENCE {
    reference       [0] IMPLICIT SEQUENCE OF ObjectReference
}

GetMSVCBValues-ResponsePDU ::= SEQUENCE {
    msvcb           [0] IMPLICIT SEQUENCE OF CHOICE {
        error       [0] IMPLICIT ServiceError,
        value       [1] IMPLICIT MSVCB
    },
    moreFollows     [1] IMPLICIT BOOLEAN DEFAULT TRUE
}

GetMSVCBValues-ErrorPDU ::= ServiceError

-- ======================================================================
-- 8.10.3 SetMSVCBValues (Service Code 0x87)
-- ======================================================================

SetMSVCBValues-RequestPDU ::= SEQUENCE {
    msvcb           [0] IMPLICIT SEQUENCE OF SEQUENCE {
        reference   [0] IMPLICIT ObjectReference,
        svEna       [1] IMPLICIT BOOLEAN OPTIONAL,
        msvID       [2] IMPLICIT VisibleString129 OPTIONAL,
        datSet      [3] IMPLICIT ObjectReference OPTIONAL,
        smpMod      [5] IMPLICIT SmpMod OPTIONAL,
        smpRate     [6] IMPLICIT INT16U OPTIONAL,
        optFlds     [7] IMPLICIT MSVCBOptFlds OPTIONAL
    }
}

SetMSVCBValues-ResponsePDU ::= NULL

SetMSVCBValues-ErrorPDU ::= SEQUENCE {
    result          [0] IMPLICIT SEQUENCE OF SEQUENCE {
        error       [0] IMPLICIT ServiceError OPTIONAL,
        svEna       [1] IMPLICIT ServiceError OPTIONAL,
        msvID       [2] IMPLICIT ServiceError OPTIONAL,
        datSet      [3] IMPLICIT ServiceError OPTIONAL,
        smpMod      [5] IMPLICIT ServiceError OPTIONAL,
        smpRate     [6] IMPLICIT ServiceError OPTIONAL,
        optFlds     [7] IMPLICIT ServiceError OPTIONAL
    }
}

-- ======================================================================
-- 8.11.1 Select (Service Code 0x21)
-- ======================================================================

Select-RequestPDU ::= SEQUENCE {
    reference       [0] IMPLICIT ObjectReference
}

Select-ResponsePDU ::= SEQUENCE {
    reference       [0] IMPLICIT ObjectReference
}

Select-ErrorPDU ::= SEQUENCE {
    reference       [0] IMPLICIT ObjectReference
}

-- ======================================================================
-- 8.11.2 SelectWithValue (Service Code 0x22)
-- ======================================================================

SelectWithValue-RequestPDU ::= SEQUENCE {
    reference       [0] IMPLICIT ObjectReference,
    ctlVal          [1] IMPLICIT Data,
    operTm          [2] IMPLICIT TimeStamp OPTIONAL,
    origin          [3] IMPLICIT Originator,
    ctlNum          [4] IMPLICIT INT8U,
    t               [5] IMPLICIT TimeStamp,
    test            [6] IMPLICIT BOOLEAN,
    check           [7] IMPLICIT Check
}

SelectWithValue-ResponsePDU ::= SEQUENCE {
    reference       [0] IMPLICIT ObjectReference,
    ctlVal          [1] IMPLICIT Data,
    operTm          [2] IMPLICIT TimeStamp OPTIONAL,
    origin          [3] IMPLICIT Originator,
    ctlNum          [4] IMPLICIT INT8U,
    t               [5] IMPLICIT TimeStamp,
    test            [6] IMPLICIT BOOLEAN,
    check           [7] IMPLICIT Check
}

SelectWithValue-ErrorPDU ::= SEQUENCE {
    reference       [0] IMPLICIT ObjectReference,
    ctlVal          [1] IMPLICIT Data,
    operTm          [2] IMPLICIT TimeStamp OPTIONAL,
    origin          [3] IMPLICIT Originator,
    ctlNum          [4] IMPLICIT INT8U,
    t               [5] IMPLICIT TimeStamp,
    test            [6] IMPLICIT BOOLEAN,
    check           [7] IMPLICIT Check,
    addCause        [8] IMPLICIT AddCause
}

-- ======================================================================
-- 8.11.3 Operate (Service Code 0x23)
-- ======================================================================

Operate-RequestPDU ::= SEQUENCE {
    reference       [0] IMPLICIT ObjectReference,
    ctlVal          [1] IMPLICIT Data,
    origin          [3] IMPLICIT Originator,
    ctlNum          [4] IMPLICIT INT8U,
    t               [5] IMPLICIT TimeStamp,
    test            [6] IMPLICIT BOOLEAN,
    check           [7] IMPLICIT Check
}

Operate-ResponsePDU ::= SEQUENCE {
    reference       [0] IMPLICIT ObjectReference
}

Operate-ErrorPDU ::= SEQUENCE {
    reference       [0] IMPLICIT ObjectReference,
    ctlVal          [1] IMPLICIT Data,
    origin          [3] IMPLICIT Originator,
    ctlNum          [4] IMPLICIT INT8U,
    t               [5] IMPLICIT TimeStamp,
    test            [6] IMPLICIT BOOLEAN,
    check           [7] IMPLICIT Check,
    addCause        [8] IMPLICIT AddCause
}

-- ======================================================================
-- 8.11.4 Cancel (Service Code 0x24)
-- ======================================================================

Cancel-RequestPDU ::= SEQUENCE {
    reference       [0] IMPLICIT ObjectReference,
    ctlVal          [1] IMPLICIT Data,
    operTm          [2] IMPLICIT TimeStamp OPTIONAL,
    origin          [3] IMPLICIT Originator,
    ctlNum          [4] IMPLICIT INT8U,
    t               [5] IMPLICIT TimeStamp,
    test            [6] IMPLICIT BOOLEAN
}

Cancel-ResponsePDU ::= SEQUENCE {
    reference       [0] IMPLICIT ObjectReference,
    ctlVal          [1] IMPLICIT Data,
    operTm          [2] IMPLICIT TimeStamp OPTIONAL,
    origin          [3] IMPLICIT Originator,
    ctlNum          [4] IMPLICIT INT8U,
    t               [5] IMPLICIT TimeStamp,
    test            [6] IMPLICIT BOOLEAN
}

Cancel-ErrorPDU ::= SEQUENCE {
    reference       [0] IMPLICIT ObjectReference,
    ctlVal          [1] IMPLICIT Data,
    operTm          [2] IMPLICIT TimeStamp OPTIONAL,
    origin          [3] IMPLICIT Originator,
    ctlNum          [4] IMPLICIT INT8U,
    t               [5] IMPLICIT TimeStamp,
    test            [6] IMPLICIT BOOLEAN,
    addCause        [8] IMPLICIT AddCause
}

-- ======================================================================
-- 8.11.5 CommandTermination (Service Code 0x26)
-- ======================================================================

CommandTermination-RequestPDU ::= SEQUENCE {
    reference       [0] IMPLICIT ObjectReference,
    ctlVal          [1] IMPLICIT Data,
    operTm          [2] IMPLICIT TimeStamp OPTIONAL,
    origin          [3] IMPLICIT Originator,
    ctlNum          [4] IMPLICIT INT8U,
    t               [5] IMPLICIT TimeStamp,
    test            [6] IMPLICIT BOOLEAN,
    check           [7] IMPLICIT Check,
    addCause        [8] IMPLICIT AddCause OPTIONAL
}

-- ======================================================================
-- 8.11.6 TimeActivatedOperate (Service Code 0x25)
-- ======================================================================

TimeActivatedOperate-RequestPDU ::= SEQUENCE {
    reference       [0] IMPLICIT ObjectReference,
    ctlVal          [1] IMPLICIT Data,
    operTm          [2] IMPLICIT TimeStamp,
    origin          [3] IMPLICIT Originator,
    ctlNum          [4] IMPLICIT INT8U,
    t               [5] IMPLICIT TimeStamp,
    test            [6] IMPLICIT BOOLEAN,
    check           [7] IMPLICIT Check
}

TimeActivatedOperate-ResponsePDU ::= SEQUENCE {
    reference       [0] IMPLICIT ObjectReference,
    ctlVal          [1] IMPLICIT Data,
    operTm          [2] IMPLICIT TimeStamp,
    origin          [3] IMPLICIT Originator,
    ctlNum          [4] IMPLICIT INT8U,
    t               [5] IMPLICIT TimeStamp,
    test            [6] IMPLICIT BOOLEAN,
    check           [7] IMPLICIT Check
}

TimeActivatedOperate-ErrorPDU ::= SEQUENCE {
    reference       [0] IMPLICIT ObjectReference,
    ctlVal          [1] IMPLICIT Data,
    operTm          [2] IMPLICIT TimeStamp,
    origin          [3] IMPLICIT Originator,
    ctlNum          [4] IMPLICIT INT8U,
    t               [5] IMPLICIT TimeStamp,
    test            [6] IMPLICIT BOOLEAN,
    check           [7] IMPLICIT Check,
    addCause        [8] IMPLICIT AddCause
}

-- ======================================================================
-- 8.11.7 TimeActivatedOperateTermination (Service Code 0x27)
-- ======================================================================

TimeActivatedOperateTermination-RequestPDU ::= SEQUENCE {
    reference       [0] IMPLICIT ObjectReference,
    ctlVal          [1] IMPLICIT Data,
    operTm          [2] IMPLICIT TimeStamp,
    origin          [3] IMPLICIT Originator,
    ctlNum          [4] IMPLICIT INT8U,
    t               [5] IMPLICIT TimeStamp,
    test            [6] IMPLICIT BOOLEAN,
    check           [7] IMPLICIT Check,
    addCause        [8] IMPLICIT AddCause OPTIONAL
}

-- ======================================================================
-- 8.12.1 GetFile (Service Code 0x71)
-- ======================================================================

GetFile-RequestPDU ::= SEQUENCE {
    filename        [0] IMPLICIT VisibleString255,
    startPosition   [1] IMPLICIT INT32U
}

GetFile-ResponsePDU ::= SEQUENCE {
    fileData        [0] IMPLICIT OCTET STRING,
    endOfFile       [1] IMPLICIT BOOLEAN DEFAULT FALSE
}

GetFile-ErrorPDU ::= ServiceError

-- ======================================================================
-- 8.12.2 SetFile (Service Code 0x72)
-- ======================================================================

SetFile-RequestPDU ::= SEQUENCE {
    filename        [0] IMPLICIT VisibleString255,
    startPosition   [1] IMPLICIT INT32U,
    fileData        [2] IMPLICIT OCTET STRING,
    endOfFile       [3] IMPLICIT BOOLEAN DEFAULT FALSE
}

SetFile-ResponsePDU ::= NULL

SetFile-ErrorPDU ::= ServiceError

-- ======================================================================
-- 8.12.3 DeleteFile (Service Code 0x73)
-- ======================================================================

DeleteFile-RequestPDU ::= SEQUENCE {
    filename        [0] IMPLICIT VisibleString255
}

DeleteFile-ResponsePDU ::= NULL

DeleteFile-ErrorPDU ::= ServiceError

-- ======================================================================
-- 8.12.4 GetFileAttributeValues (Service Code 0x75)
-- ======================================================================

GetFileAttributeValues-RequestPDU ::= SEQUENCE {
    filename        [0] IMPLICIT VisibleString255
}

GetFileAttributeValues-ResponsePDU ::= FileEntry

GetFileAttributeValues-ErrorPDU ::= ServiceError

-- ======================================================================
-- 8.12.5 GetFileDirectory (Service Code 0x74)
-- ======================================================================

GetFileDirectory-RequestPDU ::= SEQUENCE {
    pathName        [0] IMPLICIT VisibleString255,
    startTime       [1] IMPLICIT TimeStamp OPTIONAL,
    stopTime        [2] IMPLICIT TimeStamp OPTIONAL,
    fileAfter       [3] IMPLICIT VisibleString255 OPTIONAL
}

GetFileDirectory-ResponsePDU ::= SEQUENCE {
    fileEntry       [0] IMPLICIT SEQUENCE OF FileEntry,
    moreFollows     [1] IMPLICIT BOOLEAN DEFAULT TRUE
}

GetFileDirectory-ErrorPDU ::= ServiceError

-- ======================================================================
-- 8.13.1 RPC Introduction
-- ======================================================================

-- introduction

-- ======================================================================
-- 8.13.2 GetRpcInterfaceDirectory (Service Code 0x91)
-- ======================================================================

GetRpcInterfaceDirectory-RequestPDU ::= SEQUENCE {
    referenceAfter  [0] IMPLICIT VisibleString OPTIONAL
}

GetRpcInterfaceDirectory-ResponsePDU ::= SEQUENCE {
    reference       [0] IMPLICIT SEQUENCE OF VisibleString,
    moreFollows     [1] IMPLICIT BOOLEAN DEFAULT TRUE
}

GetRpcInterfaceDirectory-ErrorPDU ::= ServiceError

-- ======================================================================
-- 8.11.3 GetRpcMethodDirectory (Service Code 0x93)
-- ======================================================================

GetRpcMethodDirectory-RequestPDU ::= SEQUENCE {
    interface       [0] IMPLICIT VisibleString OPTIONAL,
    referenceAfter  [1] IMPLICIT VisibleString OPTIONAL
}

GetRpcMethodDirectory-ResponsePDU ::= SEQUENCE {
    reference       [0] IMPLICIT SEQUENCE OF VisibleString,
    moreFollows     [1] IMPLICIT BOOLEAN DEFAULT TRUE
}

GetRpcMethodDirectory-ErrorPDU ::= ServiceError

-- ======================================================================
-- 8.13.4 GetRpcInterfaceDefinition (Service Code 0x92)
-- ======================================================================

GetRpcInterfaceDefinition-RequestPDU ::= SEQUENCE {
    interface       [0] IMPLICIT VisibleString,
    referenceAfter  [1] IMPLICIT VisibleString OPTIONAL
}

GetRpcInterfaceDefinition-ResponsePDU ::= SEQUENCE {
    method          [0] IMPLICIT SEQUENCE OF SEQUENCE {
        name        [0] IMPLICIT VisibleString,
        version     [1] IMPLICIT INT32U,
        timeout     [2] IMPLICIT INT32U,
        request     [3] IMPLICIT DataDefinition,
        response    [4] IMPLICIT DataDefinition
    },
    moreFollows     [1] IMPLICIT BOOLEAN DEFAULT TRUE
}

GetRpcInterfaceDefinition-ErrorPDU ::= ServiceError

-- ======================================================================
-- 8.11.4 GetRpcMethodDefinition (Service Code 0x94)
-- ======================================================================

GetRpcMethodDefinition-RequestPDU ::= SEQUENCE {
    reference       [0] IMPLICIT SEQUENCE OF VisibleString
}

GetRpcMethodDefinition-ResponsePDU ::= SEQUENCE {
    reference       [0] IMPLICIT SEQUENCE OF CHOICE {
        error       [0] IMPLICIT ServiceError,
        method      [1] IMPLICIT SEQUENCE {
            version     [0] IMPLICIT INT32U,
            timeout     [1] IMPLICIT INT32U,
            request     [2] IMPLICIT DataDefinition,
            response    [3] IMPLICIT DataDefinition
        }
    },
    moreFollows     [1] IMPLICIT BOOLEAN DEFAULT TRUE
}

GetRpcMethodDefinition-ErrorPDU ::= ServiceError

-- ======================================================================
-- 8.11.5 RpcCall (Service Code 0x95)
-- ======================================================================

RpcCall-RequestPDU ::= SEQUENCE {
    method          [0] IMPLICIT VisibleString,
    req             [1] IMPLICIT CHOICE {
        reqData     [0] IMPLICIT Data,
        callID      [1] IMPLICIT OCTET STRING
    }
}

RpcCall-ResponsePDU ::= SEQUENCE {
    rspData         [0] IMPLICIT Data,
    nextCallID      [1] IMPLICIT OCTET STRING OPTIONAL
}

RpcCall-ErrorPDU ::= ServiceError

-- ======================================================================
-- 8.14 Test (Service Code 0xA1)
-- ======================================================================

-- FL = 0, no field

-- ======================================================================
-- 8.13 AssociateNegotiate (Service Code 0x04)
-- ======================================================================

AssociateNegotiate-RequestPDU ::= SEQUENCE {
    apduSize        [0] IMPLICIT INT16U,
    asduSize        [1] IMPLICIT INT32U,
    protocolVersion [2] IMPLICIT INT32U
}

AssociateNegotiate-ResponsePDU ::= SEQUENCE {
    apduSize        [0] IMPLICIT INT16U,
    asduSize        [1] IMPLICIT INT32U,
    protocolVersion [2] IMPLICIT INT32U,
    modelVersion    [3] IMPLICIT VisibleString
}

AssociateNegotiate-ErrorPDU ::= ServiceError

END
