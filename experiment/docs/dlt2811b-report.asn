--
-- DL/T 2811 Report Services — BRCB / URCB / Report
--

DLT2811-Report { 1 2 156 2811 6 } DEFINITIONS AUTOMATIC TAGS ::= BEGIN

IMPORTS
    Int8U, Int16U, Int16, Int32U, VisibleString, OctetString,
    BOOLEAN, ObjectReference, EntryTime, EntryID,
    RcbOptFlds, TriggerConditions, ReasonCode, Quality,
    ServiceError, Dbpos, Tcmd, Check, Data, UtcTime
    FROM DLT2811-DataTypes;

-- ======================================================================
-- 8.5.1 GetBRCBValues (Service Code 0x31)
-- ======================================================================

-- Mapped to: CmsGetBRCBValues (Java)

GetBRCBValues-Request ::= SEQUENCE {
    reqId                       Int16U,
    brcbRef                     ObjectReference
}

GetBRCBValues-ResponsePositive ::= SEQUENCE {
    reqId                       Int16U,
    brcbName                    ObjectReference,
    rptID                       VisibleString (SIZE(0..129)),
    rptEna                      BOOLEAN,
    datSet                      ObjectReference,
    confRev                     Int32U,
    optFlds                     RcbOptFlds,
    bufTm                       Int32U,
    sqNum                       Int16U,
    trgOps                      TriggerConditions,
    intgPd                      Int32U,
    gi                          BOOLEAN,
    purgeBuf                    BOOLEAN,
    entryID                     EntryID,
    timeOfEntry                 EntryTime,
    owner                       OCTET STRING (SIZE(64))
}

GetBRCBValues-ResponseNegative ::= SEQUENCE {
    reqId                       Int16U,
    serviceError                ServiceError
}

-- ======================================================================
-- 8.5.2 SetBRCBValues (Service Code 0x32)
-- ======================================================================

-- Mapped to: CmsSetBRCBValues (Java)

SetBRCBValues-Entry ::= SEQUENCE {
    reference                   ObjectReference,
    rptEna                      BOOLEAN OPTIONAL,
    rptID                       VisibleString (SIZE(0..129)) OPTIONAL,
    datSet                      ObjectReference OPTIONAL,
    confRev                     Int32U OPTIONAL,
    optFlds                     RcbOptFlds OPTIONAL,
    bufTm                       Int32U OPTIONAL,
    trgOps                      TriggerConditions OPTIONAL,
    intgPd                      Int32U OPTIONAL,
    gi                          BOOLEAN OPTIONAL,
    purgeBuf                    BOOLEAN OPTIONAL,
    entryID                     EntryID OPTIONAL,
    timeOfEntry                 EntryTime OPTIONAL,
    reserved                    BOOLEAN OPTIONAL
}

SetBRCBValues-Request ::= SEQUENCE {
    reqId                       Int16U,
    brcbValues                  SEQUENCE OF SetBRCBValues-Entry
}

SetBRCBValues-ResponsePositive ::= SEQUENCE {
    reqId                       Int16U
}

SetBRCBValues-ResponseNegative ::= SEQUENCE {
    reqId                       Int16U,
    serviceError                ServiceError
}

-- ======================================================================
-- 8.5.3 GetURCBValues (Service Code 0x33)
-- ======================================================================

-- Mapped to: CmsGetURCBValues (Java)

GetURCBValues-Request ::= SEQUENCE {
    reqId                       Int16U,
    urcbRef                     ObjectReference
}

GetURCBValues-ResponsePositive ::= SEQUENCE {
    reqId                       Int16U,
    urcbName                    ObjectReference,
    rptID                       VisibleString (SIZE(0..129)),
    rptEna                      BOOLEAN,
    datSet                      ObjectReference,
    confRev                     Int32U,
    optFlds                     RcbOptFlds,
    bufTm                       Int32U,
    sqNum                       Int8U,
    trgOps                      TriggerConditions,
    intgPd                      Int32U,
    gi                          BOOLEAN,
    owner                       OCTET STRING (SIZE(64))
}

GetURCBValues-ResponseNegative ::= SEQUENCE {
    reqId                       Int16U,
    serviceError                ServiceError
}

-- ======================================================================
-- 8.5.4 SetURCBValues (Service Code 0x34)
-- ======================================================================

-- Mapped to: CmsSetURCBValues (Java)

SetURCBValues-Entry ::= SEQUENCE {
    reference                   ObjectReference,
    rptEna                      BOOLEAN OPTIONAL,
    rptID                       VisibleString (SIZE(0..129)) OPTIONAL,
    datSet                      ObjectReference OPTIONAL,
    confRev                     Int32U OPTIONAL,
    optFlds                     RcbOptFlds OPTIONAL,
    bufTm                       Int32U OPTIONAL,
    trgOps                      TriggerConditions OPTIONAL,
    intgPd                      Int32U OPTIONAL,
    gi                          BOOLEAN OPTIONAL,
    reserved                    BOOLEAN OPTIONAL
}

SetURCBValues-Request ::= SEQUENCE {
    reqId                       Int16U,
    urcbValues                  SEQUENCE OF SetURCBValues-Entry
}

SetURCBValues-ResponsePositive ::= SEQUENCE {
    reqId                       Int16U
}

SetURCBValues-ResponseNegative ::= SEQUENCE {
    reqId                       Int16U,
    serviceError                ServiceError
}

-- ======================================================================
-- 8.5.5 Report (Service Code 0x35, unconfirmed)
-- ======================================================================

-- Mapped to: CmsReport (Java)

ReportEntryData ::= SEQUENCE {
    dataRef                     ObjectReference,
    entryData                   Data,
    reasonCode                  ReasonCode,
    dataQuality                 Quality OPTIONAL,
    dataTime                    EntryTime OPTIONAL
}

ReportEntry ::= SEQUENCE {
    entryID                     EntryID,
    entryTime                   EntryTime,
    entryData                   SEQUENCE OF ReportEntryData
}

Report ::= SEQUENCE {
    reqId                       Int16U,
    rptID                       VisibleString (SIZE(0..129)),
    optFlds                     RcbOptFlds,
    sqNum                       Int16U,
    subSQNum                    Int8U,
    moreSegmentsFollow          BOOLEAN,
    entry                       SEQUENCE OF ReportEntry
}

END
