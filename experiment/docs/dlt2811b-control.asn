--
-- DL/T 2811 Control Services — Select / Operate / Cancel / CommandTermination
--

DLT2811-Control { 1 2 156 2811 5 } DEFINITIONS AUTOMATIC TAGS ::= BEGIN

IMPORTS
    Int8U, Int16U, Int32U, VisibleString, OctetString,
    Data, ObjectReference, ServiceError, Tcmd, Check, OrCat
    FROM DLT2811-DataTypes;

-- ======================================================================
-- 8.4.1 Select (Service Code 0x21)
-- ======================================================================

-- Mapped to: CmsSelect (Java)

Select-Request ::= SEQUENCE {
    reqId                       Int16U,
    actCode                     Tcmd,
    actRef                      ObjectReference,
    actData                     Data OPTIONAL
}

Select-ResponsePositive ::= SEQUENCE {
    reqId                       Int16U,
    actCnf                      Check
}

Select-ResponseNegative ::= SEQUENCE {
    reqId                       Int16U,
    serviceError                ServiceError
}

-- ======================================================================
-- 8.4.2 SelectWithValue (Service Code 0x22)
-- ======================================================================

-- Mapped to: CmsSelectWithValue (Java)

SelectWithValue-Request ::= SEQUENCE {
    reqId                       Int16U,
    actCode                     Tcmd,
    actRef                      ObjectReference,
    actData                     Data
}

SelectWithValue-ResponsePositive ::= SEQUENCE {
    reqId                       Int16U,
    actCnf                      Check
}

SelectWithValue-ResponseNegative ::= SEQUENCE {
    reqId                       Int16U,
    serviceError                ServiceError
}

-- ======================================================================
-- 8.4.3 Operate (Service Code 0x23)
-- ======================================================================

-- Mapped to: CmsOperate (Java)

Operate-Request ::= SEQUENCE {
    reqId                       Int16U,
    actCode                     Tcmd,
    actRef                      ObjectReference,
    actData                     OPTIONAL,
    orCat                       OrCat,
    orIdent                     OctetString (SIZE(0..64))
}

Operate-ResponsePositive ::= SEQUENCE {
    reqId                       Int16U,
    actCnf                      Check
}

Operate-ResponseNegative ::= SEQUENCE {
    reqId                       Int16U,
    serviceError                ServiceError
}

-- ======================================================================
-- 8.4.4 Cancel (Service Code 0x24)
-- ======================================================================

-- Mapped to: CmsCancel (Java)

Cancel-Request ::= SEQUENCE {
    reqId                       Int16U,
    actRef                      ObjectReference,
    actCode                     Tcmd
}

Cancel-ResponsePositive ::= SEQUENCE {
    reqId                       Int16U,
    actCnf                      Check
}

Cancel-ResponseNegative ::= SEQUENCE {
    reqId                       Int16U,
    serviceError                ServiceError
}

-- ======================================================================
-- 8.4.5 TimeActivatedOperate (Service Code 0x25)
-- ======================================================================

-- Mapped to: CmsTimeActivatedOperate (Java)

TimeActivatedOperate-Request ::= SEQUENCE {
    reqId                       Int16U,
    actCode                     Tcmd,
    actRef                      ObjectReference,
    actData                     Data OPTIONAL,
    orCat                       OrCat,
    orIdent                     OctetString (SIZE(0..64)),
    tActTm                      UtcTime
}

TimeActivatedOperate-ResponsePositive ::= SEQUENCE {
    reqId                       Int16U,
    actCnf                      Check
}

TimeActivatedOperate-ResponseNegative ::= SEQUENCE {
    reqId                       Int16U,
    serviceError                ServiceError
}

-- ======================================================================
-- 8.4.6 CommandTermination (Service Code 0x26)
-- ======================================================================

-- Mapped to: CmsCommandTermination (Java)
-- Unconfirmed service (server → client)

CommandTermination ::= SEQUENCE {
    reqId                       Int16U,
    actRef                      ObjectReference,
    actCnf                      Check,
    actData                     Data OPTIONAL
}

-- ======================================================================
-- 8.4.7 TimeActivatedOperateTermination (Service Code 0x27)
-- ======================================================================

-- Mapped to: CmsTimeActivatedOperateTermination (Java)
-- Unconfirmed service (server → client)

TimeActivatedOperateTermination ::= SEQUENCE {
    reqId                       Int16U,
    actRef                      ObjectReference,
    actCnf                      Check,
    tActTm                      UtcTime,
    actData                     Data OPTIONAL
}

END
