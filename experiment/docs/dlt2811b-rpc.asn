--
-- DL/T 2811 RPC Services — RpcCall / GetRpcInterface / GetRpcMethod
--

DLT2811-Rpc { 1 2 156 2811 12 } DEFINITIONS AUTOMATIC TAGS ::= BEGIN

IMPORTS
    Int8U, Int16U, Int32U, VisibleString, OctetString,
    ObjectReference, ServiceError, Data
    FROM DLT2811-DataTypes;

-- ======================================================================
-- 8.11.1 GetRpcInterfaceDirectory (Service Code 0x91)
-- ======================================================================

-- Mapped to: CmsGetRpcInterfaceDirectory (Java)

GetRpcInterfaceDirectory-Request ::= SEQUENCE {
    reqId                       Int16U
}

GetRpcInterfaceDirectory-ResponsePositive ::= SEQUENCE {
    reqId                       Int16U,
    interfaces                  SEQUENCE OF VisibleString (SIZE(0..64))
}

GetRpcInterfaceDirectory-ResponseNegative ::= SEQUENCE {
    reqId                       Int16U,
    serviceError                ServiceError
}

-- ======================================================================
-- 8.11.2 GetRpcInterfaceDefinition (Service Code 0x92)
-- ======================================================================

-- Mapped to: CmsGetRpcInterfaceDefinition (Java)

RpcMethodDefEntry ::= SEQUENCE {
    methodName                  VisibleString (SIZE(0..64)),
    inputTypes                  SEQUENCE OF VisibleString (SIZE(0..32)),
    outputTypes                 SEQUENCE OF VisibleString (SIZE(0..32))
}

GetRpcInterfaceDefinition-Request ::= SEQUENCE {
    reqId                       Int16U,
    interfaceName               VisibleString (SIZE(0..64))
}

GetRpcInterfaceDefinition-ResponsePositive ::= SEQUENCE {
    reqId                       Int16U,
    interfaceName               VisibleString (SIZE(0..64)),
    methods                     SEQUENCE OF RpcMethodDefEntry
}

GetRpcInterfaceDefinition-ResponseNegative ::= SEQUENCE {
    reqId                       Int16U,
    serviceError                ServiceError
}

-- ======================================================================
-- 8.11.3 GetRpcMethodDirectory (Service Code 0x93)
-- ======================================================================

-- Mapped to: CmsGetRpcMethodDirectory (Java)

GetRpcMethodDirectory-Request ::= SEQUENCE {
    reqId                       Int16U,
    interfaceName               VisibleString (SIZE(0..64)),
    methodName                  VisibleString (SIZE(0..64))
}

GetRpcMethodDirectory-ResponsePositive ::= SEQUENCE {
    reqId                       Int16U,
    methodName                  VisibleString (SIZE(0..64))
}

GetRpcMethodDirectory-ResponseNegative ::= SEQUENCE {
    reqId                       Int16U,
    serviceError                ServiceError
}

-- ======================================================================
-- 8.11.4 GetRpcMethodDefinition (Service Code 0x94)
-- ======================================================================

-- Mapped to: CmsGetRpcMethodDefinition (Java)

RpcMethodValue ::= SEQUENCE {
    paramName                   VisibleString (SIZE(0..64)),
    paramType                   VisibleString (SIZE(0..32)),
    paramValue                  Data OPTIONAL
}

GetRpcMethodDefinition-Request ::= SEQUENCE {
    reqId                       Int16U,
    interfaceName               VisibleString (SIZE(0..64)),
    methodName                  VisibleString (SIZE(0..64))
}

GetRpcMethodDefinition-ResponsePositive ::= SEQUENCE {
    reqId                       Int16U,
    interfaceName               VisibleString (SIZE(0..64)),
    methodName                  VisibleString (SIZE(0..64)),
    parameters                  SEQUENCE OF RpcMethodValue
}

GetRpcMethodDefinition-ResponseNegative ::= SEQUENCE {
    reqId                       Int16U,
    serviceError                ServiceError
}

-- ======================================================================
-- 8.11.5 RpcCall (Service Code 0x95)
-- ======================================================================

-- Mapped to: CmsRpcCall (Java)

RpcCall-Request ::= SEQUENCE {
    reqId                       Int16U,
    interfaceName               VisibleString (SIZE(0..64)),
    methodName                  VisibleString (SIZE(0..64)),
    parameters                  SEQUENCE OF RpcMethodValue
}

RpcCall-ResponsePositive ::= SEQUENCE {
    reqId                       Int16U,
    responseValues              SEQUENCE OF RpcMethodValue
}

RpcCall-ResponseNegative ::= SEQUENCE {
    reqId                       Int16U,
    serviceError                ServiceError
}

-- ======================================================================
-- 8.12.1 Test (Service Code 0xA1)
-- ======================================================================

Test-Request ::= SEQUENCE {
    reqId                       Int16U
}

Test-ResponsePositive ::= SEQUENCE {
    reqId                       Int16U,
    testResult                  BOOLEAN
}

Test-ResponseNegative ::= SEQUENCE {
    reqId                       Int16U,
    serviceError                ServiceError
}

END
