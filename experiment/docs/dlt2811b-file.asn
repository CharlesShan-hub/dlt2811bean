--
-- DL/T 2811 File Services — GetFile / SetFile / DeleteFile / GetFileDirectory / GetFileAttributeValues
--

DLT2811-File { 1 2 156 2811 10 } DEFINITIONS AUTOMATIC TAGS ::= BEGIN

IMPORTS
    Int8U, Int16U, Int32U, VisibleString, OctetString,
    ObjectReference, ServiceError, UtcTime
    FROM DLT2811-DataTypes;

-- ======================================================================
-- 8.9.1 GetFile (Service Code 0x71)
-- ======================================================================

-- Mapped to: CmsGetFile (Java)

GetFile-Request ::= SEQUENCE {
    reqId                       Int16U,
    fileName                    VisibleString (SIZE(0..255))
}

GetFile-ResponsePositive ::= SEQUENCE {
    reqId                       Int16U,
    fileSize                    Int32U,
    fileData                    OCTET STRING (SIZE(0..65535))
}

GetFile-ResponseNegative ::= SEQUENCE {
    reqId                       Int16U,
    serviceError                ServiceError
}

-- ======================================================================
-- 8.9.2 SetFile (Service Code 0x72)
-- ======================================================================

-- Mapped to: CmsSetFile (Java)

SetFile-Request ::= SEQUENCE {
    reqId                       Int16U,
    fileName                    VisibleString (SIZE(0..255)),
    fileData                    OCTET STRING (SIZE(0..65535))
}

SetFile-ResponsePositive ::= SEQUENCE {
    reqId                       Int16U,
    fileSize                    Int32U
}

SetFile-ResponseNegative ::= SEQUENCE {
    reqId                       Int16U,
    serviceError                ServiceError
}

-- ======================================================================
-- 8.9.3 DeleteFile (Service Code 0x73)
-- ======================================================================

-- Mapped to: CmsDeleteFile (Java)

DeleteFile-Request ::= SEQUENCE {
    reqId                       Int16U,
    fileName                    VisibleString (SIZE(0..255))
}

DeleteFile-ResponsePositive ::= SEQUENCE {
    reqId                       Int16U
}

DeleteFile-ResponseNegative ::= SEQUENCE {
    reqId                       Int16U,
    serviceError                ServiceError
}

-- ======================================================================
-- 8.9.4 GetFileDirectory (Service Code 0x74)
-- ======================================================================

-- Mapped to: CmsGetFileDirectory (Java)

FileAttribute ::= SEQUENCE {
    fileName                    VisibleString (SIZE(0..255)),
    fileSize                    Int32U,
    lastModified                UtcTime OPTIONAL
}

GetFileDirectory-Request ::= SEQUENCE {
    reqId                       Int16U,
    directoryName               VisibleString (SIZE(0..255))
}

GetFileDirectory-ResponsePositive ::= SEQUENCE {
    reqId                       Int16U,
    files                       SEQUENCE OF FileAttribute
}

GetFileDirectory-ResponseNegative ::= SEQUENCE {
    reqId                       Int16U,
    serviceError                ServiceError
}

-- ======================================================================
-- 8.9.5 GetFileAttributeValues (Service Code 0x75)
-- ======================================================================

-- Mapped to: CmsGetFileAttributeValues (Java)

GetFileAttributeValues-Request ::= SEQUENCE {
    reqId                       Int16U,
    fileName                    VisibleString (SIZE(0..255))
}

GetFileAttributeValues-ResponsePositive ::= SEQUENCE {
    reqId                       Int16U,
    fileAttributes              FileAttribute
}

GetFileAttributeValues-ResponseNegative ::= SEQUENCE {
    reqId                       Int16U,
    serviceError                ServiceError
}

END
